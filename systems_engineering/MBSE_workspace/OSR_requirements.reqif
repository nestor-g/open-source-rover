# Specification: Operational Analysis Requirements

## REQ-OA-011-01
Operator shall assess visible terrain for obstacles before commanding motion into any new area.
- Layer: OA
- Status: DRAFT

## REQ-OA-011-02
Operator shall define a traverse path avoiding obstacles exceeding the rover's mobility limits.
- Layer: OA
- Status: DRAFT

## REQ-OA-011-03
A go/no-go decision shall be made and communicated before each traverse segment.
- Layer: OA
- Status: DRAFT

## REQ-OA-012-01
Operator shall command rover motion using a single handheld controller.
- Layer: OA
- Status: DRAFT

## REQ-OA-012-02
Motion commands shall be transmitted with round-trip latency ≤ 200 ms under nominal Wi-Fi.
- Layer: OA
- Status: DRAFT

## REQ-OA-012-03
Rover shall come to a complete stop within 1 s of operator releasing the motion command.
- Layer: OA
- Status: DRAFT

## REQ-OA-012-04
Rover shall execute a commanded stop within 1 s if the wireless link is lost.
- Layer: OA
- Status: DRAFT

## REQ-OA-013-01
Operator shall receive rover telemetry updates at ≥ 5 Hz during active operation.
- Layer: OA
- Status: DRAFT

## REQ-OA-013-02
Battery state-of-charge shall be visible on the ground station display at all times.
- Layer: OA
- Status: DRAFT

## REQ-OA-013-03
Any fault condition shall produce a visible alert on the ground station within one telemetry cycle.
- Layer: OA
- Status: DRAFT

## REQ-OA-013-04
Operator shall distinguish normal from fault operating states from ground station display alone.
- Layer: OA
- Status: DRAFT

## REQ-OA-014-01
Operator shall issue a stop command within 3 s of recognising a hazard condition.
- Layer: OA
- Status: DRAFT

## REQ-OA-014-02
Operator shall acknowledge all system-generated fault events before resuming rover motion.
- Layer: OA
- Status: DRAFT

## REQ-OA-014-03
A clear recovery procedure shall exist for each fault type.
- Layer: OA
- Status: DRAFT

## REQ-OA-015-01
Rover shall stream live camera video to ground station at ≥ 10 fps during operation.
- Layer: OA
- Status: DRAFT

## REQ-OA-015-02
All sensor data shall be time-stamped with the rover's system clock.
- Layer: OA
- Status: DRAFT

## REQ-OA-015-03
Collected data shall be accessible for download via SSH after mission completion.
- Layer: OA
- Status: DRAFT

## REQ-OA-021-01
Battery shall be charged using a balance charger with cell-level voltage monitoring.
- Layer: OA
- Status: DRAFT

## REQ-OA-021-02
Charge rate shall not exceed 1C.
- Layer: OA
- Status: DRAFT

## REQ-OA-021-03
Battery shall not be charged while installed in rover unless a dedicated charge circuit with thermal monitoring is present.
- Layer: OA
- Status: DRAFT

## REQ-OA-021-04
A fully charged 3S LiPo shall measure ≥ 12.6 V at pack terminals.
- Layer: OA
- Status: DRAFT

## REQ-OA-022-01
A hardware inspection shall be performed after every operating session involving terrain traverse.
- Layer: OA
- Status: DRAFT

## REQ-OA-022-02
Any loose fastener shall be re-torqued before the next mission.
- Layer: OA
- Status: DRAFT

## REQ-OA-022-03
Worn or damaged components shall be replaced before rover is returned to service.
- Layer: OA
- Status: DRAFT

## REQ-OA-023-01
Software updates shall be deployed via SSH without requiring physical disassembly.
- Layer: OA
- Status: DRAFT

## REQ-OA-023-02
After any update, all ROS nodes shall be verified running before returning rover to service.
- Layer: OA
- Status: DRAFT

## REQ-OA-023-03
Post-update functional test shall include ≥ 0.5 m commanded forward motion and full stop.
- Layer: OA
- Status: DRAFT

## REQ-OA-031-01
All sourced components shall meet or exceed BOM specifications.
- Layer: OA
- Status: DRAFT

## REQ-OA-031-02
Builder shall verify received quantities against BOM before beginning assembly.
- Layer: OA
- Status: DRAFT

## REQ-OA-031-03
Substitute components shall be verified compatible before use.
- Layer: OA
- Status: DRAFT

## REQ-OA-032-01
Mechanical assembly shall be completable using only standard hand tools.
- Layer: OA
- Status: DRAFT

## REQ-OA-032-02
All pivot joints shall use flanged bearings.
- Layer: OA
- Status: DRAFT

## REQ-OA-032-03
All structural fasteners shall be tightened to finger-tight plus 1/4 turn unless otherwise specified.
- Layer: OA
- Status: DRAFT

## REQ-OA-032-04
Completed chassis shall support rover total mass without visible deflection.
- Layer: OA
- Status: DRAFT

## REQ-OA-033-01
A continuity check shall be performed on all power rails before applying battery power for the first time.
- Layer: OA
- Status: DRAFT

## REQ-OA-033-02
Wire gauges shall meet or exceed the minimum specified in the harness guide.
- Layer: OA
- Status: DRAFT

## REQ-OA-033-03
An in-line fuse (≤ 30 A) shall be installed between battery and PCB input.
- Layer: OA
- Status: DRAFT

## REQ-OA-033-04
All motor and servo connectors shall be secured with positive-retention connectors.
- Layer: OA
- Status: DRAFT

## REQ-OA-034-01
Software installation shall be completable following the documented guide without prior ROS expertise.
- Layer: OA
- Status: DRAFT

## REQ-OA-034-02
All ROS nodes shall start without errors on first launch after fresh installation.
- Layer: OA
- Status: DRAFT

## REQ-OA-034-03
Rover shall respond to /cmd_vel within 5 minutes of completing software installation.
- Layer: OA
- Status: DRAFT

## REQ-OA-034-04
Wi-Fi connectivity and SSH access shall be confirmed before launching ROS.
- Layer: OA
- Status: DRAFT

## REQ-OA-041-01
Payload designs shall not exceed power budget allocations.
- Layer: OA
- Status: DRAFT

## REQ-OA-041-02
Mechanical payload attachments shall use the standard M3 bolt pattern without permanent chassis modification.
- Layer: OA
- Status: DRAFT

## REQ-OA-041-03
Design package shall include a defined ROS data interface (topic name, message type, update rate).
- Layer: OA
- Status: DRAFT

## REQ-OA-041-04
Payload mass shall be documented; total rover mass with payload shall not exceed 10 kg.
- Layer: OA
- Status: DRAFT

## REQ-OA-042-01
Payload integration shall not require removal or permanent modification of any baseline rover component.
- Layer: OA
- Status: DRAFT

## REQ-OA-042-02
All payload wiring shall be routed clear of rotating and articulating components.
- Layer: OA
- Status: DRAFT

## REQ-OA-042-03
Payload integration shall be reversible using only a standard Allen key set.
- Layer: OA
- Status: DRAFT

## REQ-OA-043-01
Custom ROS nodes shall be added to OSR catkin workspace without modifying existing baseline nodes.
- Layer: OA
- Status: DRAFT

## REQ-OA-043-02
New ROS topics shall follow the OSR naming convention.
- Layer: OA
- Status: DRAFT

## REQ-OA-043-03
All custom nodes shall handle startup and shutdown gracefully.
- Layer: OA
- Status: DRAFT

## REQ-OA-043-04
A README shall document all new topics, configurable parameters, and their data types.
- Layer: OA
- Status: DRAFT

# Specification: System Function Requirements

## REQ-SF-01-01
System shall accept motion commands as geometry_msgs/Twist on /cmd_vel.
- Layer: SF
- Status: DRAFT

## REQ-SF-01-02
System shall apply a 1-second command watchdog, outputting zero velocity on timeout.
- Layer: SF
- Status: DRAFT

## REQ-SF-01-03
System shall discard command messages containing NaN or Inf values.
- Layer: SF
- Status: DRAFT

## REQ-SF-01-04
System shall process command messages at a minimum rate of 10 Hz.
- Layer: SF
- Status: DRAFT

## REQ-SF-02-01
System shall compute per-wheel speed setpoints using the OSR rocker-bogie kinematic model.
- Layer: SF
- Status: DRAFT

## REQ-SF-02-02
Drive wheel setpoints shall be updated at ≥ 20 Hz.
- Layer: SF
- Status: DRAFT

## REQ-SF-02-03
System shall clamp drive setpoints to motor controller rated maximum speed.
- Layer: SF
- Status: DRAFT

## REQ-SF-02-04
System shall position corner steering servos to Ackermann-correct angles within 250 ms.
- Layer: SF
- Status: DRAFT

## REQ-SF-02-05
Upon halt signal from SF-06, SF-02 shall set all drive motor setpoints to zero within ≤ 50 ms.
- Layer: SF
- Status: DRAFT

## REQ-SF-03-01
System shall provide regulated 5V ± 5% to RPi and logic peripherals.
- Layer: SF
- Status: DRAFT

## REQ-SF-03-02
System shall read and publish battery voltage and current at ≥ 1 Hz.
- Layer: SF
- Status: DRAFT

## REQ-SF-03-03
System shall compute and publish state-of-charge as a percentage from LiPo discharge curve.
- Layer: SF
- Status: DRAFT

## REQ-SF-03-04
System shall trigger safe stop when any motor current exceeds 10 A.
- Layer: SF
- Status: DRAFT

## REQ-SF-03-05
System shall publish low-battery warning when voltage falls below 11.0 V.
- Layer: SF
- Status: DRAFT

## REQ-SF-03-06
System shall trigger safe stop when battery voltage falls below 10.5 V.
- Layer: SF
- Status: DRAFT

## REQ-SF-04-01
System shall sample wheel encoder counts at ≥ 20 Hz per wheel.
- Layer: SF
- Status: DRAFT

## REQ-SF-04-02
System shall sample IMU acceleration and gyroscope at ≥ 50 Hz.
- Layer: SF
- Status: DRAFT

## REQ-SF-04-03
System shall publish odometry (/odom) at ≥ 10 Hz.
- Layer: SF
- Status: DRAFT

## REQ-SF-04-04
System shall publish attitude (/imu) at ≥ 20 Hz.
- Layer: SF
- Status: DRAFT

## REQ-SF-04-05
System shall publish telemetry topics to ground station at ≥ 5 Hz.
- Layer: SF
- Status: DRAFT

## REQ-SF-04-06
Telemetry latency from sensor read to Wi-Fi transmission shall not exceed 200 ms.
- Layer: SF
- Status: DRAFT

## REQ-SF-05-01
System shall capture and publish video at ≥ 15 fps at 640x480 when camera is installed.
- Layer: SF
- Status: DRAFT

## REQ-SF-05-02
System shall publish compressed video on /camera/image_raw/compressed.
- Layer: SF
- Status: DRAFT

## REQ-SF-05-03
Video stream latency shall not exceed 500 ms over local Wi-Fi.
- Layer: SF
- Status: DRAFT

## REQ-SF-05-04
System shall start without error when camera is absent; SF-05 shall be inactive without affecting other functions.
- Layer: SF
- Status: DRAFT

## REQ-SF-06-01
System shall monitor motor channel current at ≥ 10 Hz.
- Layer: SF
- Status: DRAFT

## REQ-SF-06-02
System shall trigger safe stop within 100 ms of any motor current exceeding 10 A.
- Layer: SF
- Status: DRAFT

## REQ-SF-06-03
System shall publish battery warning at < 11.0 V and trigger safe stop at < 10.5 V.
- Layer: SF
- Status: DRAFT

## REQ-SF-06-04
System shall monitor rover roll and pitch at ≥ 10 Hz.
- Layer: SF
- Status: DRAFT

## REQ-SF-06-05
System shall trigger safe stop within 100 ms of roll or pitch exceeding 35°.
- Layer: SF
- Status: DRAFT

## REQ-SF-06-06
Upon safe stop, system shall zero all drive motor setpoints and publish fault event to /diagnostics.
- Layer: SF
- Status: DRAFT

## REQ-SF-06-07
Safe stop shall latch; rover shall not resume motion until operator clear command is received and fault resolved.
- Layer: SF
- Status: DRAFT

## REQ-SF-07-01
System shall provide switchable 5V @ ≥ 2 A and 12V @ ≥ 2 A to payload connector.
- Layer: SF
- Status: DRAFT

## REQ-SF-07-02
System shall monitor payload current and disable rail if exceeding configured limit (default 2 A).
- Layer: SF
- Status: DRAFT

## REQ-SF-07-03
System shall provide USB, I2C, and UART connectivity to payload from Raspberry Pi.
- Layer: SF
- Status: DRAFT

## REQ-SF-07-04
Payload power enable/disable shall be controllable via software (GPIO).
- Layer: SF
- Status: DRAFT

## REQ-SF-07-05
Payload power rail switching shall not interrupt or reset any other system power rail.
- Layer: SF
- Status: DRAFT

# Specification: Logical Component Requirements

## REQ-LC-01-01
LC-01 shall receive motion commands from ground station on /cmd_vel.
- Layer: LC
- Status: DRAFT

## REQ-LC-01-02
LC-01 shall detect command stream timeout and notify LC-02 to command zero velocity.
- Layer: LC
- Status: DRAFT

## REQ-LC-01-03
LC-01 shall relay all outbound telemetry topics to ground station at their respective publish rates.
- Layer: LC
- Status: DRAFT

## REQ-LC-01-04
LC-01 shall relay video stream from LC-08 when SF-05 is active.
- Layer: LC
- Status: DRAFT

## REQ-LC-01-05
LC-01 shall not drop or reorder command packets at distances ≤ 50 m.
- Layer: LC
- Status: DRAFT

## REQ-LC-02-01
LC-02 shall parse geometry_msgs/Twist and extract linear.x and angular.z.
- Layer: LC
- Status: DRAFT

## REQ-LC-02-02
LC-02 shall discard messages containing NaN or Inf values.
- Layer: LC
- Status: DRAFT

## REQ-LC-02-03
LC-02 shall clamp linear.x to ±0.4 m/s and angular.z to ±1.0 rad/s.
- Layer: LC
- Status: DRAFT

## REQ-LC-02-04
LC-02 shall output zero velocity to LC-03 immediately upon halt command from LC-05.
- Layer: LC
- Status: DRAFT

## REQ-LC-02-05
LC-02 shall output zero velocity to LC-03 when LC-01 signals watchdog timeout.
- Layer: LC
- Status: DRAFT

## REQ-LC-03-01
LC-03 shall compute per-wheel speed setpoints using the OSR rocker-bogie kinematic model.
- Layer: LC
- Status: DRAFT

## REQ-LC-03-02
LC-03 shall compute Ackermann steering angles for all four corner wheels.
- Layer: LC
- Status: DRAFT

## REQ-LC-03-03
LC-03 shall update drive wheel setpoints at ≥ 20 Hz.
- Layer: LC
- Status: DRAFT

## REQ-LC-03-04
LC-03 shall update steering servo angles within 250 ms of angular velocity change.
- Layer: LC
- Status: DRAFT

## REQ-LC-03-05
LC-03 shall clamp wheel speed setpoints to motor controller rated maximum.
- Layer: LC
- Status: DRAFT

## REQ-LC-03-06
LC-03 shall clamp steering angles to each servo's mechanical range (±30°).
- Layer: LC
- Status: DRAFT

## REQ-LC-03-07
LC-03 shall output zero speed to all wheels immediately upon halt command.
- Layer: LC
- Status: DRAFT

## REQ-LC-04-01
LC-04 shall read wheel encoder counts from all six wheels at ≥ 20 Hz.
- Layer: LC
- Status: DRAFT

## REQ-LC-04-02
LC-04 shall read IMU acceleration and angular velocity at ≥ 50 Hz.
- Layer: LC
- Status: DRAFT

## REQ-LC-04-03
LC-04 shall read per-channel motor currents at ≥ 10 Hz.
- Layer: LC
- Status: DRAFT

## REQ-LC-04-04
LC-04 shall publish nav_msgs/Odometry at ≥ 10 Hz.
- Layer: LC
- Status: DRAFT

## REQ-LC-04-05
LC-04 shall publish sensor_msgs/Imu at ≥ 20 Hz.
- Layer: LC
- Status: DRAFT

## REQ-LC-04-06
LC-04 shall publish per-motor current readings to LC-05 at ≥ 10 Hz.
- Layer: LC
- Status: DRAFT

## REQ-LC-04-07
Odometry position error shall not exceed 10% of distance travelled in straight-line test.
- Layer: LC
- Status: DRAFT

## REQ-LC-05-01
LC-05 shall monitor motor currents at ≥ 10 Hz and trigger safe stop within 100 ms of 10 A threshold.
- Layer: LC
- Status: DRAFT

## REQ-LC-05-02
LC-05 shall monitor battery voltage at ≥ 1 Hz, warn at < 11.0 V, and stop at < 10.5 V.
- Layer: LC
- Status: DRAFT

## REQ-LC-05-03
LC-05 shall monitor roll and pitch at ≥ 10 Hz and trigger safe stop within 100 ms of 35° threshold.
- Layer: LC
- Status: DRAFT

## REQ-LC-05-04
All critical faults shall latch; halt persists until clear_fault service call is received.
- Layer: LC
- Status: DRAFT

## REQ-LC-05-05
LC-05 shall verify fault condition resolved before responding to clear_fault.
- Layer: LC
- Status: DRAFT

## REQ-LC-05-06
LC-05 shall publish all fault events with timestamp and classification to /diagnostics.
- Layer: LC
- Status: DRAFT

## REQ-LC-06-01
LC-06 shall read battery voltage and current from INA219 at ≥ 1 Hz.
- Layer: LC
- Status: DRAFT

## REQ-LC-06-02
LC-06 shall publish sensor_msgs/BatteryState on /battery_state.
- Layer: LC
- Status: DRAFT

## REQ-LC-06-03
LC-06 shall compute SoC% using 3S LiPo discharge curve (100% at ≥ 12.6 V, 0% at ≤ 10.5 V).
- Layer: LC
- Status: DRAFT

## REQ-LC-06-04
LC-06 shall provide software-controllable enable/disable for payload power rail.
- Layer: LC
- Status: DRAFT

## REQ-LC-06-05
LC-06 voltage measurement accuracy shall be within ±0.1 V of multimeter reference.
- Layer: LC
- Status: DRAFT

## REQ-LC-07-01
LC-07 shall publish aggregated diagnostic summary at ≥ 5 Hz.
- Layer: LC
- Status: DRAFT

## REQ-LC-07-02
LC-07 shall include battery state, fault flags, odometry, attitude, and motor currents in telemetry.
- Layer: LC
- Status: DRAFT

## REQ-LC-07-03
LC-07 shall relay video frames from LC-08 when SF-05 is active.
- Layer: LC
- Status: DRAFT

## REQ-LC-07-04
LC-07 shall not introduce more than 50 ms of additional latency to sensor topic data.
- Layer: LC
- Status: DRAFT

## REQ-LC-08-01
LC-08 shall provide GPIO-controlled 5V and 12V power rails to payload connector.
- Layer: LC
- Status: DRAFT

## REQ-LC-08-02
LC-08 shall monitor payload current at ≥ 1 Hz and disable rail if exceeding limit (default 2 A).
- Layer: LC
- Status: DRAFT

## REQ-LC-08-03
LC-08 shall publish a fault event to /diagnostics on payload overcurrent.
- Layer: LC
- Status: DRAFT

## REQ-LC-08-04
LC-08 shall provide USB, I2C, and UART pass-through from payload connector to RPi.
- Layer: LC
- Status: DRAFT

## REQ-LC-08-05
Payload power switching shall not affect any other power rail or reset the Raspberry Pi.
- Layer: LC
- Status: DRAFT
